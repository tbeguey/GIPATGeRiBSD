FME workspace bsd.fmw

Parameters:
- SourceDataset_MDB_ADO = Y:\20. BASE_ASA\ASA\2k_ASA.mdb   # Fichier(s) source Microsoft Access Database 
- DestDataset_POSTGRES = bsd   # Base de données 

Readers:
- MDB_ADO_1: MDB_ADO from $(SourceDataset_MDB_ADO)

Writers:
- POSTGRES_1: POSTGRES to $(DestDataset_POSTGRES)

TYPE_DONNEES_ECHANGE (reader MDB_ADO_1)
    attributes: no_type_donnees_echange long, type_donnees_echange_libelle text(255), ThemeInspireAbrege text(50), CategorieIso19115 long, ThemeInspire text(255), Gestionnaire text(255), Observation text(255), Donnees_metier_CDC yesno, Donnees_metier_etat yesno, NATURE_DONNEEGIP long
    -> bsd.type_donnees_echange (writer POSTGRES_1)
Note: Flux de données
bsd.type_donnees_echange (writer POSTGRES_1)
    attributes: no_type_donnees_echange int4, type_donnees_echange_libelle varchar(255), themeinspireabrege varchar(50), categorieiso19115 int4, themeinspire varchar(255), gestionnaire varchar(255), observation varchar(255), donnees_metier_cdc bool, donnees_metier_etat bool, nature_donneegip int4
TB_PIGMA_SUIVI (reader MDB_ADO_1)
    attributes: pigma_NoEntreprise long, pigma_cible yesno, pigma_date_1er_contact datetime, pigma_date_dernier_contact datetime, pigma_interesse text(3), pigma_id autonumber, pigma_segmentation long, pigma_interet_couchebasse yesno, pigma_interet_web yesno, pigma_interet_grouptravail yesno, pigma_interet_catalogage yesno, pigma_convention_date_relance datetime, pigma_zone_competence_geoconcept long, pigma_strategie_animation text(50)
    -> bsd.tb_pigma_suivi (writer POSTGRES_1)
bsd.tb_pigma_suivi (writer POSTGRES_1)
    attributes: pigma_noentreprise int4, pigma_cible bool, pigma_date_1er_contact timestamp, pigma_date_dernier_contact timestamp, pigma_interesse varchar(3), pigma_id int4, pigma_segmentation int4, pigma_interet_couchebasse bool, pigma_interet_web bool, pigma_interet_grouptravail bool, pigma_interet_catalogage bool, pigma_convention_date_relance timestamp, pigma_zone_competence_geoconcept int4, pigma_strategie_animation varchar(50)
PIGMA_DONNEES_A_DISPO (reader MDB_ADO_1)
    attributes: id_entreprise long, type_donnee long, conventionnee yesno, catalogue yesno, livree yesno, non_publiee yesno, fichier_geographique yesno, it_geonetwork yesno, it_geoserver yesno, integree_ids_wms_externe yesno, date_integration datetime, autre_ids yesno, membregip yesno, serviceetat yesno, colect_territ yesno, etab_public yesno, secteur_associatif yesno, grand_public yesno, autre memo, Nom_autre_ids text(255), minifiche yesno, opendata yesno, date_reception datetime, format_donnees text(255), projection_donnees text(255)
    -> bsd.pigma_donnees_a_dispo_init (writer POSTGRES_1)
bsd.pigma_donnees_a_dispo_init (writer POSTGRES_1)
    attributes: id_entreprise int4, type_donnee int4, conventionnee bool, catalogue bool, livree bool, non_publiee bool, fichier_geographique bool, it_geonetwork bool, it_geoserver bool, integree_ids_wms_externe bool, date_integration timestamp, autre_ids bool, membregip bool, serviceetat bool, colect_territ bool, etab_public bool, secteur_associatif bool, grand_public bool, autre text, nom_autre_ids varchar(255), minifiche bool, opendata bool, date_reception timestamp, format_donnees varchar(255), projection_donnees varchar(255)
ENTREPRISE (reader MDB_ADO_1)
    attributes: No Entreprise long, Entreprise text(100), Entreprise_Abrege text(100), Codeactivité long, Code postalE text(5), VilleE text(30), Adres1E text(40), Adres2E text(40), CodePays long, TélE text(16), FaxE text(16), Article entreprise text(20), Code STATUT entreprise long, No TRESORERIE long, RIB1 text(30), RIB2 text(30), N_MAIRIE_SIEGE_ASA long, Compterr_id long, whocreated text(30), xl93 double, yl93 double, foretdata yesno, CODE_SIREN text(254), CODE_NAF text(254), NUM_TVA_INTRA text(254), pefc yesno, astreinte yesno, ami yesno, civb integer, cvi_evv text(255)
    -> bsd.entreprise_contact (writer POSTGRES_1)
bsd.entreprise_contact (writer POSTGRES_1)
    attributes: no_entreprise int4, entreprise varchar(100), entreprise_abrege varchar(100), codeactivité int4, code_postale varchar(5), villee varchar(30), adres1e varchar(40), adres2e varchar(40), codepays int4, téle varchar(16), faxe varchar(16), article_entreprise varchar(20), code_statut_entreprise int4, no_tresorerie int4, rib1 varchar(30), rib2 varchar(30), n_mairie_siege_asa int4, compterr_id int4, whocreated varchar(30), xl93 float8, yl93 float8, foretdata bool, code_siren varchar(254), code_naf varchar(254), num_tva_intra varchar(254), pefc bool, astreinte bool, ami bool, civb int2, cvi_evv varchar(255)
