FME workspace geonetwork.fmw

Parameters:
- SourceDataset_POSTGRES = georchestra   # Base de données 
- DestDataset_POSTGRES = bsd   # Base de données 

Readers:
- POSTGRES_1: POSTGRES from $(SourceDataset_POSTGRES)

Writers:
- POSTGRES_2: POSTGRES to $(DestDataset_POSTGRES)

geonetwork.metadata (reader POSTGRES_1)
    attributes: id int4,PRIKEY, uuid varchar(250),PRIKEY, schemaid varchar(32), istemplate char(1), isharvested char(1), createdate varchar(30), changedate varchar(30), data text, source varchar(250),BTREE, title varchar(255), root varchar(255), harvestuuid varchar(250), owner int4,BTREE, groupowner int4, harvesturi varchar(512), rating int4, popularity int4, displayorder int4, doctype varchar(255)
    -> geonetwork.metadata_init (writer POSTGRES_2)
Note: Flux de données
geonetwork.metadata_init (writer POSTGRES_2)
    attributes: id int4,PRIKEY, uuid varchar(250),PRIKEY, schemaid varchar(32), istemplate char(1), isharvested char(1), createdate varchar(30), changedate varchar(30), data text, source varchar(250),BTREE, title varchar(255), root varchar(255), harvestuuid varchar(250), owner int4,BTREE, groupowner int4, harvesturi varchar(512), rating int4, popularity int4, displayorder int4, doctype varchar(255)
