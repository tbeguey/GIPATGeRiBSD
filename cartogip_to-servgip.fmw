FME workspace cartogip_to-servgip.fmw

Parameters:
- SourceDataset_POSTGRES = cartogip   # Connection
- DestDataset_POSTGRES = servgip_2   # Connection

Readers:
- POSTGRES_1: POSTGRES from $(SourceDataset_POSTGRES)

Writers:
- POSTGRES_2: POSTGRES to $(DestDataset_POSTGRES)

administration_visionneuse.sys_info_viso_couche_chapitre_export (reader POSTGRES_1)
    attributes: visionneuse_id int4, visionneuse_nom varchar(40), description varchar(200), id_couche int4, nom_couche varchar(50), couche_libelle varchar(70), copyright varchar(80), copyright_annee_min int4, copyright_annee_max int4, sys_date_create date, sys_date_maj date, visio_couche_id int4, ordre int4, libelle_chapitre varchar(255), couche_annuelle bool
    -> cartogip.sys_info_viso_couche_chapitre_export (writer POSTGRES_2)
cartogip.sys_info_viso_couche_chapitre_export (writer POSTGRES_2)
    attributes: visionneuse_id int4, visionneuse_nom varchar(40), description varchar(200), id_couche int4, nom_couche varchar(50), couche_libelle varchar(70), copyright varchar(80), copyright_annee_min int4, copyright_annee_max int4, sys_date_create date, sys_date_maj date, visio_couche_id int4, ordre int4, libelle_chapitre varchar(255), couche_annuelle bool
administration_visionneuse.sys_info_visionnseuse_export (reader POSTGRES_1)
    attributes: visionneuse_id int4, visionneuse_nom varchar(40), description varchar(200), publique bool, sys_date_create date, sys_date_maj date, en_service bool
    -> cartogip.sys_info_visionnseuse_export (writer POSTGRES_2)
cartogip.sys_info_visionnseuse_export (writer POSTGRES_2)
    attributes: visionneuse_id int4, visionneuse_nom varchar(40), description varchar(200), publique bool, sys_date_create date, sys_date_maj date, en_service bool
administration_visionneuse.sys_info_visio_couche_export (reader POSTGRES_1)
    attributes: visionneuse_id int4, visionneuse_nom varchar(40), description varchar(200), id_couche int4, nom_couche varchar(50), couche_libelle varchar(70), copyright varchar(80), copyright_annee_min int4, copyright_annee_max int4, sys_date_create date, sys_date_maj date, visio_couche_id int4, ordre int4, couche_annuelle bool
    -> cartogip.sys_info_visio_couche_export (writer POSTGRES_2)
cartogip.sys_info_visio_couche_export (writer POSTGRES_2)
    attributes: visionneuse_id int4, visionneuse_nom varchar(40), description varchar(200), id_couche int4, nom_couche varchar(50), couche_libelle varchar(70), copyright varchar(80), copyright_annee_min int4, copyright_annee_max int4, sys_date_create date, sys_date_maj date, visio_couche_id int4, ordre int4, couche_annuelle bool
administration_visionneuse.sys_info_couche_export (reader POSTGRES_1)
    attributes: id_couche int4, nom_couche varchar(50), couche_libelle varchar(70), raster bool, copyright varchar(80), copyright_annee_min int4, copyright_annee_max int4, sys_date_create date, sys_date_maj date, en_service bool, couche_annuelle bool
    -> cartogip.sys_info_couche_export (writer POSTGRES_2)
cartogip.sys_info_couche_export (writer POSTGRES_2)
    attributes: id_couche int4, nom_couche varchar(50), couche_libelle varchar(70), raster bool, copyright varchar(80), copyright_annee_min int4, copyright_annee_max int4, sys_date_create date, sys_date_maj date, en_service bool, couche_annuelle bool
administration_visionneuse.couche (reader POSTGRES_1)
    attributes: id_couche serial,PRIKEY, nom_couche varchar(50), couche_libelle varchar(70), format varchar(50), transparent bool, isbaselayer bool, minscale int4, maxscale int4, icon varchar(20), id_couche_parent int4, couche_schema varchar(80), couche_table varchar(80), couche_vue_metadata varchar(80), couche_champs_geom varchar(80), geom_type varchar(80), table_clef varchar(80), copyright varchar(80), lien_fichier_externe varchar(80), opacity int4, classitem varchar(80), taille_proportionnelle_echelle bool, ponctuel_pour_poligon int4, couche_champs_libelle varchar(80),BTREE, labelitem varchar(80), labelmaxscale varchar(80), wms_couches varchar(80), id_serveur_wms int4, filter varchar(80), filter_session varchar(80), copyright_annee_min int4,
      copyright_annee_max int4, couche_base varchar(20), id_geosource int4, tooltip varchar(80), raster bool, en_cache bool, extent varchar(80), ajout_saisie_id_visionneuse varchar(80), afficher_dans_arbre_couche bool, wmts bool, epsg varchar(80), sys_date_create date, sys_date_maj date, en_service bool, filtre_groupe bool, couche_annuelle bool, wfs bool, actualiser_on bool, actualiser_delai_defaut int4
    -> cartogip.couche (writer POSTGRES_2)
cartogip.couche (writer POSTGRES_2)
    attributes: id_couche serial,PRIKEY, nom_couche varchar(50), couche_libelle varchar(70), format varchar(50), transparent bool, isbaselayer bool, minscale int4, maxscale int4, icon varchar(20), id_couche_parent int4, couche_schema varchar(80), couche_table varchar(80), couche_vue_metadata varchar(80), couche_champs_geom varchar(80), geom_type varchar(80), table_clef varchar(80), copyright varchar(80), lien_fichier_externe varchar(80), opacity int4, classitem varchar(80), taille_proportionnelle_echelle bool, ponctuel_pour_poligon int4, couche_champs_libelle varchar(80),BTREE, labelitem varchar(80), labelmaxscale varchar(80), wms_couches varchar(80), id_serveur_wms int4, filter varchar(80), filter_session varchar(80), copyright_annee_min int4,
      copyright_annee_max int4, couche_base varchar(20), id_geosource int4, tooltip varchar(80), raster bool, en_cache bool, extent varchar(80), ajout_saisie_id_visionneuse varchar(80), afficher_dans_arbre_couche bool, wmts bool, epsg varchar(80), sys_date_create date, sys_date_maj date, en_service bool, filtre_groupe bool, couche_annuelle bool, wfs bool, actualiser_on bool, actualiser_delai_defaut int4
